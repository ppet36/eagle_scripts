/**
 * ULP script for generating holes and cut of PCB.
 *
 * @author ppet36
*/

/* Parameters. */

// Cutter diameters
real drillToolDiameter = 0.8;
real cutToolDiameter = 1.5;

// Feeds & speeds
int cutFeed = 400;
int drillFeed = 100;
int circularFeed = 150;
int spindleSpeed = 12000;
int spindleDelaySec = 8;

// Sizes & locations
real zHigh = 25.0;
real zSafe = 5.0;
real zAct = 0.5;
real zIncDrill = 0.5;
real drillDepth = -2;
real cutTabSize = 5.0;


void header() {
  printf ("(Generated by drills_mills.ulp)\n");
  printf ("G21\n");
  printf ("G17\n");
  printf ("G0 Z%f\n", zHigh);
  printf ("M3 S%d\n", spindleSpeed);
  printf ("G4 P%d\n", spindleDelaySec);
}

void footer() {
  printf ("G0 Z%f\n", zHigh);
  printf ("M5\n");
  printf ("M30\n\n");
}

void hole (int _diam, int _x, int _y) {
  real diam = u2mm(_diam);
  real x = -1.0 * u2mm(_x);
  real y = u2mm(_y);

  real offY = (diam / 2.0) - (drillToolDiameter / 2.0);
  real realY = y - offY;

  printf ("(hole %f at %fx%f)\n", diam, x, y);

  printf ("G0 Z%f\n", zSafe);
  printf ("G0 X%f Y%f\n", x, realY);
  printf ("G0 Z%f\n", zAct);

  if (diam <= drillToolDiameter) {
    printf ("G1 Z%f F%d\n", drillDepth, drillFeed);
  } else {
    int first = 1;
    real curDepth = zAct;
    while (curDepth > drillDepth) {
      curDepth -= zIncDrill;
      
      if (curDepth < drillDepth) {
        curDepth = drillDepth;
      }

      if (curDepth != 0) {
        printf ("G2 X%f Y%f Z%f I0 J%f", x, realY, curDepth, offY);

        if (first == 1) {
          first = 0;
          printf (" F%d\n", circularFeed);
        } else {
          printf ("\n");
        }
      }
    }

    printf ("G2 X%f Y%f I0 J%f\n", x, realY, offY);
  }
}

void cut (real x1, real y1, real x2, real y2) {
  printf ("G0 Z%f\n", zSafe);

  printf ("G0 X%f Y%f\n", x1, y1);
  printf ("G0 Z%f\n", zAct);
  printf ("G1 X%f Z-1.0 F%d\n", x2, cutFeed);
  printf ("G1 Y%f\n", y2);
  printf ("G1 X%f\n", x1);
  printf ("G1 Y%f\n", y1);
  printf ("G1 X%f\n", x2);
  printf ("G1 Y%f Z-2.0\n", y2);

  real halfX = (x2 - x1) / 2.0;
  real halfY = (y2 - y1) / 2.0;

  printf ("G1 X%f\n", x1 + halfX + cutTabSize);
  printf ("G1 X%f Z-1.0\n", x1 + halfX);
  printf ("G1 X%f Z-2.0\n", x1 + halfX - cutTabSize);
  printf ("G1 X%f\n", x1);

  printf ("G1 Y%f\n", y1 + halfY + cutTabSize);
  printf ("G1 Y%f Z-1.0\n", y1 + halfY);
  printf ("G1 Y%f Z-2.0\n", y1 + halfY - cutTabSize);
  printf ("G1 Y%f\n", y1);

  printf ("G1 X%f\n", x2 - halfX - cutTabSize);
  printf ("G1 X%f Z-1.0\n", x2 - halfX);
  printf ("G1 X%f Z-2.0\n", x2 - halfX + cutTabSize);
  printf ("G1 X%f\n", x2);    

  printf ("G1 Y%f\n", y2 - halfY - cutTabSize);
  printf ("G1 Y%f Z-1.0\n", y2 - halfY);
  printf ("G1 Y%f Z-2.0\n", y2 - halfY + cutTabSize);
  printf ("G1 Y%f\n", y2);
}

board (B) {
  output (filesetext (B.name, "_drill.gcode"), "wt") {
    header();

    B.holes (H) {
      hole (H.drill, H.x, H.y);
    }

    B.signals (S) {
      S.vias (V) {
        hole (V.drill, V.x, V.y);
      }
    }
    
    B.elements (E) {
      E.package.contacts (C) {
        if (C.pad) {
          hole (C.pad.drill, C.pad.x, C.pad.y);
        }
      }
      E.package.holes (H) {
        hole (H.drill, H.x, H.y);
      }
    }

    footer();
  }

  output (filesetext (B.name, "_cut.gcode"), "wt") {
    header();

    real minX = 99999.0;
    real minY = 99999.0;
    real maxX = -99999.0;
    real maxY = -99999.0;

    B.wires (W) {
      if (W.width == 0) {
        real x1 = -1.0 * u2mm(W.x1);
        real y1 = u2mm(W.y1);
        real x2 = -1.0 * u2mm(W.x2);
        real y2 = u2mm(W.y2);

        minX = min (minX, x1);
        minX = min (minX, x2);
        maxX = max (maxX, x1);
        maxY = max (maxX, x2); 

        minY = min (minY, y1);
        minY = min (minY, y2);
        maxY = max (maxY, y1);
        maxY = max (maxY, y2); 
      }
    }

    cut (minX, minY, maxX, maxY);

    footer();
  }
}
